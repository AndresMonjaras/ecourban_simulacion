# -*- coding: utf-8 -*-
"""Ejecuta tres mallas y guarda resultados reales de CalculiX."""

import csv
import glob
import json
import math
import os
import re
import sys
import traceback

import FreeCAD as App
import ObjectsFem
import femmesh.gmshtools as gmshtools
from femsolver.run import run_fem_solver

RAIZ = "/mnt/BancaPET/Proyectos/Prueba_001_CuboPET"
RUTA_CONFIG = os.path.join(RAIZ, "config", "caso.json")
RUTA_CAD = os.path.join(RAIZ, "cad", "cubo_100mm.FCStd")
DIR_MALLAS = os.path.join(RAIZ, "mallas")
DIR_SIMULACIONES = os.path.join(RAIZ, "simulaciones")
DIR_RESULTADOS = os.path.join(RAIZ, "resultados")
DIR_EVIDENCIAS = os.path.join(RAIZ, "evidencias")
NIVELES = [("M1", 20.0), ("M2", 10.0), ("M3", 5.0)]
TOL_CARA_MM = 1e-6
TOL_REACCION_RELATIVA = 0.01


def log(mensaje):
    App.Console.PrintMessage("[FEM] " + str(mensaje) + "\n")


def fallar(codigo, mensaje):
    App.Console.PrintError("[FEM][ERROR] " + str(mensaje) + "\n")
    sys.exit(codigo)


def leer_configuracion():
    if not os.path.isfile(RUTA_CONFIG):
        fallar(2, "No existe config/caso.json")
    with open(RUTA_CONFIG, "r", encoding="utf-8") as archivo:
        return json.load(archivo)


def copiar_geometria():
    if not os.path.isfile(RUTA_CAD):
        fallar(3, "Falta cad/cubo_100mm.FCStd; ejecute ejecutar_simulacion.sh")
    documento = App.openDocument(RUTA_CAD)
    try:
        cubo = documento.getObject("Cubo_PET_100mm")
        if cubo is None:
            fallar(4, "No se encontró Cubo_PET_100mm en el FCStd")
        forma = cubo.Shape.copy()
    finally:
        App.closeDocument(documento.Name)

    caja = forma.BoundBox
    if not forma.isValid() or len(forma.Solids) != 1:
        fallar(5, "La geometría CAD no es un sólido válido")
    if any(abs(valor - 100.0) > TOL_CARA_MM
           for valor in (caja.XLength, caja.YLength, caja.ZLength)):
        fallar(6, "La geometría CAD no mide exactamente 100 mm por lado")
    return forma


def encontrar_caras_superior_e_inferior(forma):
    z_min = forma.BoundBox.ZMin
    z_max = forma.BoundBox.ZMax
    cara_inferior = None
    cara_superior = None

    for indice, cara in enumerate(forma.Faces, start=1):
        puntos = [vertice.Point for vertice in cara.Vertexes]
        if not puntos:
            continue
        if all(abs(punto.z - z_min) < TOL_CARA_MM for punto in puntos):
            cara_inferior = "Face%d" % indice
        if all(abs(punto.z - z_max) < TOL_CARA_MM for punto in puntos):
            cara_superior = "Face%d" % indice

    if not cara_inferior or not cara_superior:
        fallar(7, "No se encontraron las caras Z mínima y Z máxima")
    return cara_inferior, cara_superior


def leer_fuerzas_totales(ruta_dat):
    """Lee las líneas de fuerza total escritas por CalculiX en el .dat."""
    fuerzas = []
    with open(ruta_dat, "r", encoding="utf-8", errors="replace") as archivo:
        lineas = archivo.readlines()

    for indice, linea in enumerate(lineas):
        if not linea.strip().lower().startswith("total force"):
            continue
        coincidencia = re.search(r"for set\s+(\S+)\s+and time", linea, re.IGNORECASE)
        nombre = coincidencia.group(1) if coincidencia else "sin_nombre"
        for siguiente in lineas[indice + 1:indice + 5]:
            try:
                valores = [float(valor) for valor in siguiente.split()]
            except ValueError:
                continue
            if len(valores) == 3:
                fuerzas.append((nombre, valores))
                break
    return fuerzas


def extraer_resultado(analisis):
    resultados = [objeto for objeto in analisis.Group
                  if objeto.isDerivedFrom("Fem::FemResultObject")]
    if not resultados:
        fallar(20, "CalculiX terminó sin crear un objeto de resultados FEM")
    return resultados[-1]


def calcular_deformacion_equivalente(componentes):
    exx, eyy, ezz, exy, exz, eyz = componentes
    promedio = (exx + eyy + ezz) / 3.0
    suma = ((exx - promedio) ** 2 + (eyy - promedio) ** 2
            + (ezz - promedio) ** 2
            + 2.0 * (exy ** 2 + exz ** 2 + eyz ** 2))
    return math.sqrt(max(0.0, (2.0 / 3.0) * suma))


def guardar_campos(nivel, resultado):
    ruta_csv = os.path.join(DIR_RESULTADOS, "campos_%s.csv" % nivel)
    numeros_nodo = list(resultado.NodeNumbers)
    desplazamientos = list(resultado.DisplacementVectors)
    tensiones = list(resultado.vonMises)
    deformaciones = list(zip(
        resultado.NodeStrainXX,
        resultado.NodeStrainYY,
        resultado.NodeStrainZZ,
        resultado.NodeStrainXY,
        resultado.NodeStrainXZ,
        resultado.NodeStrainYZ,
    ))
    nodos = resultado.Mesh.FemMesh.Nodes

    if not (len(numeros_nodo) == len(desplazamientos) == len(tensiones) == len(deformaciones)):
        fallar(21, "Las listas de campos FEM tienen longitudes distintas")

    filas = []
    for indice, numero in enumerate(numeros_nodo):
        coordenada = nodos.get(numero)
        if coordenada is None:
            continue
        vector = desplazamientos[indice]
        componentes = deformaciones[indice]
        filas.append({
            "nodo": int(numero),
            "x_mm": float(coordenada.x),
            "y_mm": float(coordenada.y),
            "z_mm": float(coordenada.z),
            "ux_mm": float(vector.x),
            "uy_mm": float(vector.y),
            "uz_mm": float(vector.z),
            "desplazamiento_mm": float(vector.Length),
            "von_mises_MPa": float(tensiones[indice]),
            "deformacion_equivalente": calcular_deformacion_equivalente(componentes),
        })

    if not filas:
        fallar(22, "No se pudieron asociar los resultados con los nodos de la malla")

    campos = list(filas[0].keys())
    with open(ruta_csv, "w", newline="", encoding="utf-8") as archivo:
        escritor = csv.DictWriter(archivo, fieldnames=campos)
        escritor.writeheader()
        escritor.writerows(filas)
    return filas, ruta_csv


def validar_y_resumir(nivel, config, ruta_dat, filas, ruta_campos):
    carga = config["carga"]
    geometria = config["geometria"]
    material = config["material"]["propiedades"]
    fuerza_esperada = float(carga["fuerza_total_N"])
    lado = float(geometria["lado_mm"])
    centro_x = lado / 2.0
    centro_y = lado / 2.0
    z_superior = lado

    fuerzas = leer_fuerzas_totales(ruta_dat)
    tolerancia = fuerza_esperada * TOL_REACCION_RELATIVA
    reaccion = next((par for par in fuerzas
                     if abs(par[1][2] - fuerza_esperada) <= tolerancia), None)
    if reaccion is None:
        detalle = "; ".join("%s: Fz=%.4f N" % (nombre, vector[2])
                            for nombre, vector in fuerzas)
        fallar(23, "No se encontró reacción +%.1f N. Fuerzas: %s" % (fuerza_esperada, detalle))

    desplazamientos_superiores = [fila["uz_mm"] for fila in filas
                                    if abs(fila["z_mm"] - z_superior) < 1e-4]
    if not desplazamientos_superiores:
        fallar(24, "No se localizaron nodos de resultados en la cara superior")
    promedio_superior = sum(desplazamientos_superiores) / len(desplazamientos_superiores)
    if promedio_superior >= 0.0:
        fallar(25, "El promedio UZ superior no es descendente; revise el signo de presión")

    tensiones_superiores = [fila for fila in filas
                             if abs(fila["z_mm"] - z_superior) < 1e-4]
    nodo_central = min(tensiones_superiores,
                       key=lambda fila: (fila["x_mm"] - centro_x) ** 2
                       + (fila["y_mm"] - centro_y) ** 2)
    fuerza_z = float(reaccion[1][2])
    modulo = float(material["E_MPa"]["valor"])
    area = float(geometria["area_cara_mm2"])
    desplazamiento_analitico = fuerza_esperada * lado / (area * modulo)
    tension_analitica = fuerza_esperada / area
    von_mises_maximo = max(fila["von_mises_MPa"] for fila in filas)

    resumen = {
        "nivel": nivel,
        "tamano_max_malla_mm": next(item["tamano_max_mm"]
                                     for item in config["mallas"]["niveles"]
                                     if item["id"] == nivel),
        "nodos_resultado": len(filas),
        "desplazamiento_medio_nodal_cara_superior_mm": promedio_superior,
        "desplazamiento_maximo_magnitud_mm": max(fila["desplazamiento_mm"] for fila in filas),
        "desplazamiento_vertical_maximo_abs_mm": max(abs(fila["uz_mm"]) for fila in filas),
        "von_mises_maximo_global_MPa": von_mises_maximo,
        "von_mises_nodo_mas_cercano_centro_superior_MPa": nodo_central["von_mises_MPa"],
        "distancia_muestra_centro_superior_mm": math.sqrt(
            (nodo_central["x_mm"] - centro_x) ** 2
            + (nodo_central["y_mm"] - centro_y) ** 2),
        "deformacion_equivalente_maxima": max(fila["deformacion_equivalente"] for fila in filas),
        "reaccion_soporte_Z_N": fuerza_z,
        "fuerza_aplicada_Z_N": -fuerza_esperada,
        "error_balance_fuerza_N": fuerza_z - fuerza_esperada,
        "desplazamiento_analitico_mm": desplazamiento_analitico,
        "error_relativo_desplazamiento_analitico_pct": 100.0 * (
            abs(promedio_superior) - desplazamiento_analitico) / desplazamiento_analitico,
        "tension_nominal_analitica_MPa": tension_analitica,
        "error_relativo_von_mises_centro_pct": 100.0 * (
            nodo_central["von_mises_MPa"] - tension_analitica) / tension_analitica,
        "ruta_dat": ruta_dat,
        "ruta_campos_csv": ruta_campos,
        "set_reaccion": reaccion[0],
        "validaciones": {
            "geometria_cad_valida": True,
            "desplazamiento_descendente": promedio_superior < 0.0,
            "reaccion_equilibra_500N": abs(fuerza_z - fuerza_esperada) <= tolerancia,
        },
        "nota_tension": "El máximo global puede depender de la singularidad del apoyo fijo.",
        "nota_centro": "Tensión nodal del nodo de la cara superior más cercano a su centro.",
    }
    return resumen


def ejecutar_nivel(nivel, tamano, config, forma_cad):
    log("Inicia %s: tamaño máximo %.1f mm, elementos cuadráticos" % (nivel, tamano))
    dir_malla = os.path.join(DIR_MALLAS, nivel)
    dir_simulacion = os.path.join(DIR_SIMULACIONES, nivel)
    os.makedirs(dir_malla, exist_ok=True)
    os.makedirs(dir_simulacion, exist_ok=True)

    for patron in ("*.dat", "*.frd", "*.inp", "*.sta", "*.cvg"):
        for ruta in glob.glob(os.path.join(dir_simulacion, patron)):
            os.remove(ruta)

    nombre_doc = "CuboPET_" + nivel
    documento = App.newDocument(nombre_doc)
    cubo = documento.addObject("Part::Feature", "Cubo_PET_100mm")
    cubo.Label = "Cubo PET 100 mm - " + nivel
    cubo.Shape = forma_cad.copy()
    documento.recompute()

    cara_inferior, cara_superior = encontrar_caras_superior_e_inferior(cubo.Shape)
    analisis = ObjectsFem.makeAnalysis(documento, "Analisis")

    material = ObjectsFem.makeMaterialSolid(documento, "MaterialPET")
    datos_material = material.Material
    propiedades = config["material"]["propiedades"]
    datos_material["Name"] = "PET reciclado provisional"
    datos_material["YoungsModulus"] = "%.6f MPa" % propiedades["E_MPa"]["valor"]
    datos_material["PoissonRatio"] = "%.6f" % propiedades["nu_adimensional"]["valor"]
    datos_material["Density"] = "%.3f kg/m^3" % propiedades["rho_kg_m3"]["valor"]
    material.Material = datos_material
    analisis.addObject(material)

    fijo = ObjectsFem.makeConstraintFixed(documento, "ApoyoInferior")
    fijo.References = [(cubo, cara_inferior)]
    analisis.addObject(fijo)

    presion = ObjectsFem.makeConstraintPressure(documento, "CargaSuperior")
    presion.References = [(cubo, cara_superior)]
    presion.Pressure = "%.6f MPa" % config["carga"]["presion_equivalente_MPa"]
    presion.Reversed = False
    analisis.addObject(presion)

    malla = ObjectsFem.makeMeshGmsh(documento, "MallaGmsh_" + nivel)
    malla.Shape = cubo
    malla.CharacteristicLengthMax = "%.3f mm" % tamano
    malla.CharacteristicLengthMin = "%.3f mm" % (tamano / 5.0)
    malla.ElementOrder = "2nd"
    malla.SecondOrderLinear = False
    if hasattr(malla, "ElementDimension"):
        malla.ElementDimension = "3D"
    analisis.addObject(malla)

    solver = ObjectsFem.makeSolverCalculiXCcxTools(documento, "CalculiXCcxTools")
    solver.AnalysisType = "static"
    solver.GeometricalNonlinearity = "linear"
    solver.ThermoMechSteadyState = False
    solver.MatrixSolverType = "default"
    analisis.addObject(solver)
    documento.recompute()

    log("Genera malla %s con Gmsh" % nivel)
    gmsh = gmshtools.GmshTools(malla)
    gmsh.update_mesh_data()
    gmsh.get_tmp_file_paths(dir_malla, True)
    gmsh.get_gmsh_command()
    gmsh.write_gmsh_input_files()
    error_malla = gmsh.run_gmsh_with_geo()
    if error_malla:
        fallar(10, "Gmsh %s: %s" % (nivel, error_malla))
    gmsh.read_and_set_new_mesh()
    if not malla.FemMesh.Nodes:
        fallar(11, "Gmsh dejó la malla vacía en " + nivel)

    ruta_fcstd = os.path.join(dir_simulacion, "modelo_%s.FCStd" % nivel)
    documento.saveAs(ruta_fcstd)
    log("Malla %s: %d nodos, %d elementos" %
        (nivel, len(malla.FemMesh.Nodes), malla.FemMesh.ElementCount))

    log("Ejecuta CalculiX %s" % nivel)
    run_fem_solver(solver, working_dir=dir_simulacion)
    documento.recompute()

    archivos_dat = sorted(glob.glob(os.path.join(dir_simulacion, "*.dat")),
                          key=os.path.getmtime, reverse=True)
    archivos_frd = glob.glob(os.path.join(dir_simulacion, "*.frd"))
    if not archivos_dat or not archivos_frd:
        fallar(12, "CalculiX no generó ambos archivos .dat y .frd para " + nivel)

    resultado = extraer_resultado(analisis)
    filas, ruta_campos = guardar_campos(nivel, resultado)
    resumen = validar_y_resumir(nivel, config, archivos_dat[0], filas, ruta_campos)
    resumen["elementos_malla"] = int(malla.FemMesh.ElementCount)
    resumen["ruta_fcstd"] = ruta_fcstd
    resumen["ruta_frd"] = archivos_frd[0]

    ruta_nivel = os.path.join(DIR_RESULTADOS, "validacion_%s.json" % nivel)
    with open(ruta_nivel, "w", encoding="utf-8") as archivo:
        json.dump(resumen, archivo, indent=2, ensure_ascii=False)

    documento.save()
    App.closeDocument(documento.Name)
    log("Termina %s: UZ medio=%.8g mm; reacción Z=%.4f N" %
        (nivel, resumen["desplazamiento_medio_nodal_cara_superior_mm"],
         resumen["reaccion_soporte_Z_N"]))
    return resumen


def agregar_convergencia(resumen, config):
    for actual, anterior in zip(resumen["niveles"][1:], resumen["niveles"][:-1]):
        desplazamiento_actual = abs(actual["desplazamiento_medio_nodal_cara_superior_mm"])
        desplazamiento_anterior = abs(anterior["desplazamiento_medio_nodal_cara_superior_mm"])
        cambio_desplazamiento = abs(desplazamiento_actual - desplazamiento_anterior) / desplazamiento_actual
        tension_actual = actual["von_mises_nodo_mas_cercano_centro_superior_MPa"]
        tension_anterior = anterior["von_mises_nodo_mas_cercano_centro_superior_MPa"]
        cambio_tension = abs(tension_actual - tension_anterior) / max(abs(tension_actual), 1e-30)
        actual["comparacion_con_malla_anterior"] = {
            "nivel_anterior": anterior["nivel"],
            "cambio_relativo_desplazamiento_medio": cambio_desplazamiento,
            "cambio_relativo_von_mises_centro": cambio_tension,
            "cumple_tolerancia_2pct_desplazamiento":
                cambio_desplazamiento <= config["mallas"]["tolerancia_relativa_M2_M3"],
        }

    resumen["convergencia"] = {
        "metrica_principal": "desplazamiento medio nodal en cara superior",
        "tolerancia_relativa": config["mallas"]["tolerancia_relativa_M2_M3"],
        "M2_vs_M3_cumple": resumen["niveles"][2]["comparacion_con_malla_anterior"][
            "cumple_tolerancia_2pct_desplazamiento"],
        "nota": "El máximo global de von Mises se reporta, pero puede crecer en la singularidad del apoyo fijo.",
    }


def main():
    for carpeta in (DIR_MALLAS, DIR_SIMULACIONES, DIR_RESULTADOS, DIR_EVIDENCIAS):
        os.makedirs(carpeta, exist_ok=True)
    config = leer_configuracion()
    forma_cad = copiar_geometria()
    log("CAD verificado; volumen %.3f mm³" % forma_cad.Volume)

    resumen = {"prueba": config["prueba"]["id"], "niveles": []}
    for nivel, tamano in NIVELES:
        resumen["niveles"].append(ejecutar_nivel(nivel, tamano, config, forma_cad))
    agregar_convergencia(resumen, config)

    ruta_resumen = os.path.join(DIR_RESULTADOS, "resumen_validacion.json")
    with open(ruta_resumen, "w", encoding="utf-8") as archivo:
        json.dump(resumen, archivo, indent=2, ensure_ascii=False)
    log("Resultados guardados en " + ruta_resumen)
    log("=== SIMULACIÓN COMPLETADA ===")


try:
    main()
except SystemExit:
    raise
except Exception:
    App.Console.PrintError("[FEM][FATAL]\n" + traceback.format_exc() + "\n")
    sys.exit(99)
