# -*- coding: utf-8 -*-
"""Crea y valida el cubo paramétrico de la Prueba 001."""

import json
import os
import sys

import FreeCAD as App
import Part

RAIZ = "/mnt/BancaPET/Proyectos/Prueba_001_CuboPET"
RUTA_CONFIG = os.path.join(RAIZ, "config", "caso.json")
RUTA_FCSTD = os.path.join(RAIZ, "cad", "cubo_100mm.FCStd")
RUTA_STEP = os.path.join(RAIZ, "cad", "cubo_100mm.step")
TOLERANCIA_MM = 1e-6


def log(mensaje):
    App.Console.PrintMessage("[CAD] " + str(mensaje) + "\n")


def detener(codigo, mensaje):
    App.Console.PrintError("[CAD][ERROR] " + mensaje + "\n")
    sys.exit(codigo)


def agregar_propiedad(objeto, tipo, nombre, descripcion, valor):
    if not hasattr(objeto, nombre):
        objeto.addProperty(tipo, nombre, "Prueba 001", descripcion)
    setattr(objeto, nombre, valor)


os.makedirs(os.path.dirname(RUTA_FCSTD), exist_ok=True)
if not os.path.isfile(RUTA_CONFIG):
    detener(2, "Falta config/caso.json")

with open(RUTA_CONFIG, "r", encoding="utf-8") as archivo:
    config = json.load(archivo)

lado = float(config["geometria"]["lado_mm"])
propiedades = config["material"]["propiedades"]

nombre_doc = "Prueba_001_CuboPET"
if nombre_doc in App.listDocuments():
    App.closeDocument(nombre_doc)
doc = App.newDocument(nombre_doc)

cubo = doc.addObject("Part::Box", "Cubo_PET_100mm")
cubo.Label = "Cubo PET 100 mm - Prueba 001"
cubo.Length = lado
cubo.Width = lado
cubo.Height = lado

doc.recompute()
forma = cubo.Shape
if not forma.isValid():
    detener(3, "La forma CAD no es válida")
if len(forma.Solids) != 1:
    detener(4, "Se esperaba un sólido; se encontraron %d" % len(forma.Solids))

caja = forma.BoundBox
for eje, medida in (("X", caja.XLength), ("Y", caja.YLength), ("Z", caja.ZLength)):
    if abs(medida - lado) > TOLERANCIA_MM:
        detener(5, "%s mide %.9f mm; se esperaba %.9f mm" % (eje, medida, lado))

if abs(forma.Volume - lado ** 3) > 1e-3:
    detener(6, "El volumen no coincide con el cubo esperado")

agregar_propiedad(cubo, "App::PropertyString", "EstadoMaterial",
                  "Las propiedades no se midieron en el lote BancaPET",
                  "Provisionales; no medidos en el lote BancaPET")
agregar_propiedad(cubo, "App::PropertyFloat", "E_MPa",
                  "Módulo elástico provisional en MPa",
                  float(propiedades["E_MPa"]["valor"]))
agregar_propiedad(cubo, "App::PropertyFloat", "Poisson",
                  "Supuesto de Poisson adimensional",
                  float(propiedades["nu_adimensional"]["valor"]))
agregar_propiedad(cubo, "App::PropertyFloat", "Densidad_kg_m3",
                  "Densidad provisional comunicada por proveedor",
                  float(propiedades["rho_kg_m3"]["valor"]))
agregar_propiedad(cubo, "App::PropertyFloat", "Temperatura_C",
                  "Metadato; no se modela dependencia térmica",
                  float(config["metadatos_ensayo"]["temperatura_C"]))
agregar_propiedad(cubo, "App::PropertyFloat", "Tiempo_s",
                  "Metadato; no se modela creep",
                  float(config["metadatos_ensayo"]["tiempo_s"]))

doc.recompute()
doc.saveAs(RUTA_FCSTD)

try:
    import Import
    Import.export([cubo], RUTA_STEP)
except Exception:
    Part.export([cubo], RUTA_STEP)

if not os.path.isfile(RUTA_FCSTD) or os.path.getsize(RUTA_FCSTD) == 0:
    detener(7, "No se guardó correctamente el archivo FCStd")
if not os.path.isfile(RUTA_STEP) or os.path.getsize(RUTA_STEP) < 100:
    detener(8, "No se exportó correctamente el archivo STEP")

log("CAD válido: 1 sólido de %.3f mm por lado; volumen %.3f mm³" % (lado, forma.Volume))
log("FCStd: " + RUTA_FCSTD)
log("STEP: " + RUTA_STEP)
