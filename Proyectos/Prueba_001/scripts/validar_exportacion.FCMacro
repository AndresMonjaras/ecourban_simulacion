# -*- coding: utf-8 -*-
"""
validar_exportacion.FCMacro

Macro de validación independiente para BancaPET Prueba 001.
Comprueba la existencia y dimensiones de los artefactos CAD (FCStd, STEP)
y del modelo web 3D (GLB 2.0) correspondientes al cubo de 100 mm centrado en el origen.

Ejecución desde línea de comandos:
    FreeCADCmd scripts/validar_exportacion.FCMacro
"""

import json
import math
import os
import struct
import sys

# Importación de APIs de FreeCAD disponibles en el entorno de FreeCADCmd
try:
    import FreeCAD as App
    import Part
except ImportError:
    App = None
    Part = None

# Lista global para recopilar mensajes de fallas detectadas
LISTA_FALLAS = []


def registrar_resultado(exito, prueba, detalle=""):
    """
    Imprime el resultado (PASS / FAIL) de una comprobación individual
    y almacena las fallas para el reporte final.
    """
    estado = "PASS" if exito else "FAIL"
    mensaje = f"[{estado}] {prueba}"
    if detalle:
        mensaje += f" -> {detalle}"

    # Salida por consola de FreeCAD si está disponible, o salida estándar
    if App is not None and hasattr(App, "Console"):
        if exito:
            App.Console.PrintMessage(mensaje + "\n")
        else:
            App.Console.PrintError(mensaje + "\n")
    else:
        if exito:
            sys.stdout.write(mensaje + "\n")
        else:
            sys.stderr.write(mensaje + "\n")

    if not exito:
        LISTA_FALLAS.append(f"{prueba}: {detalle}" if detalle else prueba)


def obtener_raiz_proyecto():
    """
    Determina la ruta raíz del proyecto (Prueba_001) a partir de la ubicación
    del propio archivo macro, evitando asumir el directorio de trabajo actual (cwd).
    """
    # 1. Intentar mediante la variable global __file__
    if "__file__" in globals() and __file__:
        dir_macro = os.path.dirname(os.path.abspath(__file__))
        return os.path.dirname(dir_macro)

    # 2. Buscar en los argumentos de la línea de comandos
    for arg in sys.argv:
        if arg.endswith("validar_exportacion.FCMacro") or arg.endswith(".FCMacro"):
            if os.path.isfile(arg):
                dir_macro = os.path.dirname(os.path.abspath(arg))
                return os.path.dirname(dir_macro)

    # 3. Ruta fija estándar en el entorno de BancaPET
    ruta_fija = "/mnt/BancaPET/Proyectos/Prueba_001"
    if os.path.isdir(ruta_fija):
        return ruta_fija

    # 4. Fallback al directorio actual de ejecución
    cwd = os.path.abspath(os.getcwd())
    if os.path.basename(cwd) == "scripts":
        return os.path.dirname(cwd)
    return cwd


def comprobar_existencia_y_tamano(nombre_relativo, ruta_absoluta):
    """
    Verifica que el archivo exista en disco y que contenga datos (> 0 bytes).
    """
    if not os.path.exists(ruta_absoluta):
        registrar_resultado(False, f"Existencia de {nombre_relativo}", "El archivo no existe en la ruta esperada")
        return False

    if not os.path.isfile(ruta_absoluta):
        registrar_resultado(False, f"Existencia de {nombre_relativo}", "La ruta existe pero no es un archivo regular")
        return False

    tamano = os.path.getsize(ruta_absoluta)
    if tamano == 0:
        registrar_resultado(False, f"Contenido de {nombre_relativo}", "El archivo está vacío (0 bytes)")
        return False

    registrar_resultado(True, f"Existencia y contenido de {nombre_relativo}", f"Tamaño: {tamano} bytes")
    return True


def validar_fcstd(ruta_fcstd):
    """
    Abre cad/cubo.FCStd y verifica que contenga un objeto cubo de tipo Part::Box
    con dimensiones de 100x100x100 mm centrado en el origen (0, 0, 0).
    Garantiza el cierre del documento al finalizar.
    """
    if App is None:
        registrar_resultado(False, "FCStd: Entorno FreeCAD", "El módulo FreeCAD no está disponible; ejecute con FreeCADCmd")
        return

    doc = None
    try:
        doc = App.openDocument(ruta_fcstd)
        doc.recompute()

        # Buscar objetos derivados o de tipo Part::Box
        cajas = [
            obj for obj in doc.Objects
            if getattr(obj, "TypeId", "") == "Part::Box" or (hasattr(obj, "isDerivedFrom") and obj.isDerivedFrom("Part::Box"))
        ]

        if not cajas:
            registrar_resultado(False, "FCStd: Objeto Part::Box", "No se encontró ningún cubo Part::Box en el documento")
            return

        cubo = cajas[0]
        registrar_resultado(True, "FCStd: Objeto Part::Box", f"Encontrado objeto '{cubo.Label}' ({cubo.Name})")

        expresiones_esperadas = {
            ".Placement.Base.x": "-Length / 2",
            ".Placement.Base.y": "-Width / 2",
            ".Placement.Base.z": "-Height / 2",
        }
        expresiones_centrado = dict(cubo.ExpressionEngine)
        centrado_parametrico = all(
            expresiones_centrado.get(propiedad) == expresion
            for propiedad, expresion in expresiones_esperadas.items()
        )
        registrar_resultado(
            centrado_parametrico,
            "FCStd: Centro vinculado a dimensiones",
            str(expresiones_centrado),
        )

        # Tolerancia dimensional en milímetros
        tol_mm = 1e-3

        # Comprobar propiedades Length, Width, Height del Part::Box
        longitud = float(getattr(cubo.Length, "Value", cubo.Length))
        ancho = float(getattr(cubo.Width, "Value", cubo.Width))
        altura = float(getattr(cubo.Height, "Value", cubo.Height))

        dims_prop_ok = (
            abs(longitud - 100.0) <= tol_mm and
            abs(ancho - 100.0) <= tol_mm and
            abs(altura - 100.0) <= tol_mm
        )
        registrar_resultado(
            dims_prop_ok,
            "FCStd: Propiedades Part::Box (100x100x100 mm)",
            f"Longitud={longitud:.3f} mm, Ancho={ancho:.3f} mm, Altura={altura:.3f} mm"
        )

        # Comprobar geometría y centrado en (0, 0, 0) a través de la forma
        forma = getattr(cubo, "Shape", None)
        if forma is None or forma.isNull():
            registrar_resultado(False, "FCStd: Forma geométrica", "El objeto no posee una forma geométrica válida")
            return

        forma_valida = forma.isValid()
        registrar_resultado(forma_valida, "FCStd: Forma válida", "shape.isValid()")
        if not forma_valida:
            return

        solidos = len(forma.Solids)
        registrar_resultado(solidos == 1, "FCStd: Un sólido", f"Sólidos encontrados: {solidos}")
        if solidos != 1:
            return

        bb = forma.BoundBox
        centrado_ok = (
            abs(bb.XMin - (-50.0)) <= tol_mm and
            abs(bb.XMax - 50.0) <= tol_mm and
            abs(bb.YMin - (-50.0)) <= tol_mm and
            abs(bb.YMax - 50.0) <= tol_mm and
            abs(bb.ZMin - (-50.0)) <= tol_mm and
            abs(bb.ZMax - 50.0) <= tol_mm and
            abs(bb.Center.x) <= tol_mm and
            abs(bb.Center.y) <= tol_mm and
            abs(bb.Center.z) <= tol_mm
        )
        registrar_resultado(
            centrado_ok,
            "FCStd: Centrado en origen (0,0,0)",
            f"BoundBox X:[{bb.XMin:.3f}, {bb.XMax:.3f}], Y:[{bb.YMin:.3f}, {bb.YMax:.3f}], Z:[{bb.ZMin:.3f}, {bb.ZMax:.3f}], Centro:({bb.Center.x:.3f}, {bb.Center.y:.3f}, {bb.Center.z:.3f})"
        )

    except Exception as err:
        registrar_resultado(False, "FCStd: Apertura/Lectura", f"Error procesando FCStd: {err}")
    finally:
        # Limpieza obligatoria del documento abierto
        if doc is not None:
            try:
                App.closeDocument(doc.Name)
            except Exception:
                pass


def validar_step(ruta_step):
    """
    Importa cad/cubo.step en un documento temporal de FreeCAD, verifica su bounding box
    (100x100x100 mm centrado en el origen), y limpia los documentos abiertos al finalizar.
    """
    if App is None:
        registrar_resultado(False, "STEP: Entorno FreeCAD", "El módulo FreeCAD no está disponible; ejecute con FreeCADCmd")
        return

    nombre_doc_temp = "DocTemporal_Validacion_STEP"
    doc_step = None
    try:
        # Cerrar documento previo si existiera con el mismo nombre
        if nombre_doc_temp in App.listDocuments():
            App.closeDocument(nombre_doc_temp)

        doc_step = App.newDocument(nombre_doc_temp)

        # Importar archivo STEP mediante módulo Import o Part
        importado = False
        try:
            import Import
            Import.insert(ruta_step, doc_step.Name)
            importado = True
        except Exception:
            pass

        if not importado:
            try:
                import Part
                Part.insert(ruta_step, doc_step.Name)
                importado = True
            except Exception as e_import:
                registrar_resultado(False, "STEP: Importación", f"No se pudo insertar el STEP: {e_import}")
                return

        doc_step.recompute()

        # Recorrer formas importadas y acumular límites del Bounding Box
        cajas = []
        for obj in doc_step.Objects:
            if hasattr(obj, "Shape") and obj.Shape and not obj.Shape.isNull():
                cajas.append(obj.Shape.BoundBox)

        if not cajas:
            registrar_resultado(False, "STEP: Geometría importada", "No se encontraron formas válidas tras la importación")
            return

        min_x = min(c.XMin for c in cajas)
        max_x = max(c.XMax for c in cajas)
        min_y = min(c.YMin for c in cajas)
        max_y = max(c.YMax for c in cajas)
        min_z = min(c.ZMin for c in cajas)
        max_z = max(c.ZMax for c in cajas)

        long_x = max_x - min_x
        long_y = max_y - min_y
        long_z = max_z - min_z

        centro_x = (min_x + max_x) / 2.0
        centro_y = (min_y + max_y) / 2.0
        centro_z = (min_z + max_z) / 2.0

        tol_mm = 1e-3

        dims_ok = (
            abs(long_x - 100.0) <= tol_mm and
            abs(long_y - 100.0) <= tol_mm and
            abs(long_z - 100.0) <= tol_mm
        )
        registrar_resultado(
            dims_ok,
            "STEP: Dimensiones Bounding Box (100x100x100 mm)",
            f"X={long_x:.3f} mm, Y={long_y:.3f} mm, Z={long_z:.3f} mm"
        )

        centrado_ok = (
            abs(min_x - (-50.0)) <= tol_mm and
            abs(max_x - 50.0) <= tol_mm and
            abs(min_y - (-50.0)) <= tol_mm and
            abs(max_y - 50.0) <= tol_mm and
            abs(min_z - (-50.0)) <= tol_mm and
            abs(max_z - 50.0) <= tol_mm and
            abs(centro_x) <= tol_mm and
            abs(centro_y) <= tol_mm and
            abs(centro_z) <= tol_mm
        )
        registrar_resultado(
            centrado_ok,
            "STEP: Bounding Box centrado en origen (0,0,0)",
            f"Límites X:[{min_x:.3f}, {max_x:.3f}], Y:[{min_y:.3f}, {max_y:.3f}], Z:[{min_z:.3f}, {max_z:.3f}], Centro:({centro_x:.3f}, {centro_y:.3f}, {centro_z:.3f})"
        )

    except Exception as err:
        registrar_resultado(False, "STEP: Procesamiento", f"Error validando STEP: {err}")
    finally:
        # Limpieza obligatoria del documento temporal
        if doc_step is not None:
            try:
                App.closeDocument(doc_step.Name)
            except Exception:
                pass


def validar_glb(ruta_glb):
    """
    Lee modelos/cubo.glb como GLB 2.0 usando json y struct estándar.
    Valida:
      - Encabezado binario (magic 0x46546C67 / b'glTF', versión 2, longitud total).
      - Chunks (Chunk 0 JSON 0x4E4F534A, Chunk 1 BIN 0x004E4942).
      - Estructura de malla y atributo POSITION.
      - Unidades en metros mediante límites o vértices cercanos a [-0.05, 0.05] m por eje
        (equivalente a 100 mm centrado en el origen).
    """
    try:
        with open(ruta_glb, "rb") as f:
            contenido_glb = f.read()
    except Exception as err:
        registrar_resultado(False, "GLB: Apertura de archivo", f"No se pudo leer el archivo: {err}")
        return

    tamano_real = len(contenido_glb)
    if tamano_real < 12:
        registrar_resultado(False, "GLB: Encabezado binario", f"Archivo demasiado corto ({tamano_real} bytes)")
        return

    # 1. Validación de encabezado GLB 2.0 (12 bytes)
    magic, version, longitud_declarada = struct.unpack_from("<4sII", contenido_glb, 0)

    magic_valido = (magic == b"glTF")
    registrar_resultado(magic_valido, "GLB: Magic b'glTF' (0x46546C67)", f"Obtenido: {magic}")

    version_valida = (version == 2)
    registrar_resultado(version_valida, "GLB: Versión glTF 2.0", f"Versión: {version}")

    longitud_valida = (longitud_declarada == tamano_real)
    registrar_resultado(
        longitud_valida,
        "GLB: Longitud de encabezado coincidente con tamaño real",
        f"Encabezado={longitud_declarada} bytes, Archivo={tamano_real} bytes"
    )

    if not (magic_valido and version_valida):
        return

    # 2. Parseo de Chunks
    offset = 12
    chunks = []
    TIPO_CHUNK_JSON = 0x4E4F534A  # ASCII 'JSON'
    TIPO_CHUNK_BIN = 0x004E4942   # ASCII 'BIN\0'

    while offset < tamano_real:
        if offset + 8 > tamano_real:
            registrar_resultado(False, "GLB: Estructura de chunks", f"Chunk incompleto en offset {offset}")
            return

        chunk_len, chunk_type = struct.unpack_from("<II", contenido_glb, offset)
        offset += 8

        if offset + chunk_len > tamano_real:
            registrar_resultado(False, "GLB: Estructura de chunks", f"Longitud de chunk {chunk_len} excede archivo en offset {offset}")
            return

        chunk_datos = contenido_glb[offset : offset + chunk_len]
        tipo_bytes = struct.pack("<I", chunk_type)
        chunks.append({
            "tipo_id": chunk_type,
            "tipo_bytes": tipo_bytes,
            "datos": chunk_datos,
            "longitud": chunk_len
        })

        # Avance considerando alineación a 4 bytes del estándar GLB
        padding = (4 - (chunk_len % 4)) % 4
        offset += chunk_len + padding

    if not chunks:
        registrar_resultado(False, "GLB: Chunks presentes", "No se identificaron chunks en el contenedor GLB")
        return

    # Validar Chunk 0 (JSON obligatorio)
    chunk0 = chunks[0]
    es_chunk_json = (chunk0["tipo_id"] == TIPO_CHUNK_JSON or chunk0["tipo_bytes"] == b"JSON")
    registrar_resultado(es_chunk_json, "GLB: Chunk 0 tipo JSON", f"Tipo={chunk0['tipo_bytes']}")

    if not es_chunk_json:
        return

    try:
        texto_json = chunk0["datos"].decode("utf-8").strip()
        gltf_json = json.loads(texto_json)
        registrar_resultado(True, "GLB: Parseo sintáctico de JSON", "Estructura JSON válida")
    except Exception as err_json:
        registrar_resultado(False, "GLB: Parseo sintáctico de JSON", f"Error al decodificar: {err_json}")
        return

    # Validar Chunk 1 (BIN opcional o esperado para geometría)
    chunk_bin_datos = None
    if len(chunks) > 1:
        chunk1 = chunks[1]
        es_chunk_bin = (chunk1["tipo_id"] == TIPO_CHUNK_BIN or chunk1["tipo_bytes"] == b"BIN\x00")
        registrar_resultado(es_chunk_bin, "GLB: Chunk 1 tipo BIN", f"Tipo={chunk1['tipo_bytes']}")
        if es_chunk_bin:
            chunk_bin_datos = chunk1["datos"]

    if chunk_bin_datos is None:
        registrar_resultado(False, "GLB: Chunk BIN requerido", "No se encontró el bloque binario de geometría")
        return

    # 3. Validar malla y atributos de posiciones
    meshes = gltf_json.get("meshes", [])
    if not meshes:
        registrar_resultado(False, "GLB: Malla (meshes)", "El documento no contiene el arreglo 'meshes'")
        return

    pos_accessor_idx = None
    normal_accessor_idx = None
    indices_accessor_idx = None
    for mesh in meshes:
        primitives = mesh.get("primitives", [])
        for prim in primitives:
            attrs = prim.get("attributes", {})
            if "POSITION" in attrs:
                pos_accessor_idx = attrs["POSITION"]
                normal_accessor_idx = attrs.get("NORMAL")
                indices_accessor_idx = prim.get("indices")
                break
        if pos_accessor_idx is not None:
            break

    if pos_accessor_idx is None:
        registrar_resultado(False, "GLB: Atributo POSITION", "No se encontró el atributo POSITION en las primitivas")
        return

    registrar_resultado(True, "GLB: Atributo POSITION", f"Referenciado en accessor índice {pos_accessor_idx}")

    if normal_accessor_idx is None:
        registrar_resultado(False, "GLB: Atributo NORMAL", "La malla no referencia normales")
        return
    if indices_accessor_idx is None:
        registrar_resultado(False, "GLB: Índices de triángulos", "La malla no referencia índices")
        return

    accessors = gltf_json.get("accessors", [])
    if pos_accessor_idx >= len(accessors):
        registrar_resultado(False, "GLB: Accessor de posición", f"Índice {pos_accessor_idx} fuera de rango")
        return

    accessor_pos = accessors[pos_accessor_idx]
    tipo_acc = accessor_pos.get("type")
    comp_tipo = accessor_pos.get("componentType")
    # 5126 representa punto flotante (FLOAT de 4 bytes)
    acc_valido = (tipo_acc == "VEC3" and comp_tipo == 5126)
    registrar_resultado(
        acc_valido,
        "GLB: Formato de Accessor POSITION (VEC3 / FLOAT)",
        f"type={tipo_acc}, componentType={comp_tipo}"
    )

    # 4. Validar unidades en metros mediante límites del Accessor [-0.05, 0.05]
    # En glTF 2.0 las unidades son metros. 100 mm centrado en origen -> [-0.05, 0.05] m por eje.
    # Tolerancia en metros: 0.001 m (1 mm)
    tol_m = 0.001

    min_acc = accessor_pos.get("min")
    max_acc = accessor_pos.get("max")
    limites_accessor_ok = False

    if min_acc and max_acc and len(min_acc) == 3 and len(max_acc) == 3:
        min_ok = (
            abs(min_acc[0] - (-0.05)) <= tol_m and
            abs(min_acc[1] - (-0.05)) <= tol_m and
            abs(min_acc[2] - (-0.05)) <= tol_m
        )
        max_ok = (
            abs(max_acc[0] - 0.05) <= tol_m and
            abs(max_acc[1] - 0.05) <= tol_m and
            abs(max_acc[2] - 0.05) <= tol_m
        )
        limites_accessor_ok = min_ok and max_ok
        registrar_resultado(
            limites_accessor_ok,
            "GLB: Unidades en metros por límites de Accessor [-0.05, 0.05] m",
            f"min=[{min_acc[0]:.4f}, {min_acc[1]:.4f}, {min_acc[2]:.4f}], max=[{max_acc[0]:.4f}, {max_acc[1]:.4f}, {max_acc[2]:.4f}]"
        )
    else:
        registrar_resultado(False, "GLB: Límites min/max en Accessor", "El accessor POSITION no declara min o max")

    # 5. Validación de vértices en el buffer binario (si el chunk BIN está presente)
    if chunk_bin_datos is not None and "bufferView" in accessor_pos:
        buffer_views = gltf_json.get("bufferViews", [])
        bv_idx = accessor_pos["bufferView"]
        if bv_idx < len(buffer_views):
            bv = buffer_views[bv_idx]
            offset_base = bv.get("byteOffset", 0) + accessor_pos.get("byteOffset", 0)
            stride = bv.get("byteStride", 12) or 12
            count = accessor_pos.get("count", 0)

            vertices = []
            try:
                for i in range(count):
                    pos_v = offset_base + i * stride
                    if pos_v + 12 <= len(chunk_bin_datos):
                        vx, vy, vz = struct.unpack_from("<3f", chunk_bin_datos, pos_v)
                        vertices.append((vx, vy, vz))

                if vertices:
                    vx_min = min(v[0] for v in vertices)
                    vx_max = max(v[0] for v in vertices)
                    vy_min = min(v[1] for v in vertices)
                    vy_max = max(v[1] for v in vertices)
                    vz_min = min(v[2] for v in vertices)
                    vz_max = max(v[2] for v in vertices)

                    vertices_ok = (
                        abs(vx_min - (-0.05)) <= tol_m and
                        abs(vx_max - 0.05) <= tol_m and
                        abs(vy_min - (-0.05)) <= tol_m and
                        abs(vy_max - 0.05) <= tol_m and
                        abs(vz_min - (-0.05)) <= tol_m and
                        abs(vz_max - 0.05) <= tol_m
                    )
                    registrar_resultado(
                        vertices_ok,
                        "GLB: Vértices decodificados en rango [-0.05, 0.05] m",
                        f"{len(vertices)} vértices. X:[{vx_min:.4f}, {vx_max:.4f}], Y:[{vy_min:.4f}, {vy_max:.4f}], Z:[{vz_min:.4f}, {vz_max:.4f}]"
                    )

                    if len(vertices) != count:
                        registrar_resultado(
                            False,
                            "GLB: Cantidad de posiciones leídas",
                            f"Esperadas={count}, leídas={len(vertices)}",
                        )
            except Exception as err_v:
                registrar_resultado(False, "GLB: Extracción de vértices binarios", f"Error: {err_v}")

    # Leer el accessor de normales desde el chunk BIN.
    try:
        accessors = gltf_json.get("accessors", [])
        buffer_views = gltf_json.get("bufferViews", [])
        accessor_normales = accessors[normal_accessor_idx]
        accessor_indices = accessors[indices_accessor_idx]

        normales_validas = (
            accessor_normales.get("type") == "VEC3" and
            accessor_normales.get("componentType") == 5126
        )
        registrar_resultado(
            normales_validas,
            "GLB: Formato de Accessor NORMAL (VEC3 / FLOAT)",
            f"type={accessor_normales.get('type')}, componentType={accessor_normales.get('componentType')}",
        )
        if not normales_validas:
            return

        vista_normales = buffer_views[accessor_normales["bufferView"]]
        inicio_normales = vista_normales.get("byteOffset", 0) + accessor_normales.get("byteOffset", 0)
        stride_normales = vista_normales.get("byteStride", 12) or 12
        cantidad_normales = accessor_normales.get("count", 0)
        normales = []
        for i in range(cantidad_normales):
            inicio = inicio_normales + i * stride_normales
            normales.append(struct.unpack_from("<3f", chunk_bin_datos, inicio))

        normales_unitarias = all(
            abs(math.sqrt(nx * nx + ny * ny + nz * nz) - 1.0) <= 1e-3
            for nx, ny, nz in normales
        )
        registrar_resultado(
            normales_unitarias and len(normales) == len(vertices),
            "GLB: Normales unitarias por vértice",
            f"{len(normales)} normales para {len(vertices)} posiciones",
        )

        formato_indices = {5123: ("<H", 2), 5125: ("<I", 4)}
        componente = formato_indices.get(accessor_indices.get("componentType"))
        if accessor_indices.get("type") != "SCALAR" or componente is None:
            registrar_resultado(False, "GLB: Formato del accessor de índices", "Se esperaba SCALAR con enteros sin signo")
            return

        vista_indices = buffer_views[accessor_indices["bufferView"]]
        inicio_indices = vista_indices.get("byteOffset", 0) + accessor_indices.get("byteOffset", 0)
        formato, bytes_por_indice = componente
        cantidad_indices = accessor_indices.get("count", 0)
        indices = [
            struct.unpack_from(formato, chunk_bin_datos, inicio_indices + i * bytes_por_indice)[0]
            for i in range(cantidad_indices)
        ]

        indices_validos = (
            len(indices) >= 3 and len(indices) % 3 == 0 and
            all(0 <= indice < len(vertices) for indice in indices)
        )
        registrar_resultado(
            indices_validos,
            "GLB: Índices válidos para triángulos",
            f"{len(indices)} índices",
        )

        orientacion_hacia_fuera = indices_validos
        normales_coinciden = indices_validos
        if indices_validos:
            for i in range(0, len(indices), 3):
                ia, ib, ic = indices[i:i + 3]
                a, b, c = vertices[ia], vertices[ib], vertices[ic]
                ab = (b[0] - a[0], b[1] - a[1], b[2] - a[2])
                ac = (c[0] - a[0], c[1] - a[1], c[2] - a[2])
                normal_cara = (
                    ab[1] * ac[2] - ab[2] * ac[1],
                    ab[2] * ac[0] - ab[0] * ac[2],
                    ab[0] * ac[1] - ab[1] * ac[0],
                )
                centro = ((a[0] + b[0] + c[0]) / 3.0,
                          (a[1] + b[1] + c[1]) / 3.0,
                          (a[2] + b[2] + c[2]) / 3.0)
                hacia_fuera = sum(normal_cara[e] * centro[e] for e in range(3)) > 0.0
                orientacion_hacia_fuera = orientacion_hacia_fuera and hacia_fuera

                magnitud = math.sqrt(sum(valor * valor for valor in normal_cara))
                normal_media = tuple(
                    (normales[ia][e] + normales[ib][e] + normales[ic][e]) / 3.0
                    for e in range(3)
                )
                alineacion = sum(normal_cara[e] * normal_media[e] for e in range(3))
                normales_coinciden = normales_coinciden and magnitud > 1e-12 and alineacion > 0.0

        registrar_resultado(
            orientacion_hacia_fuera,
            "GLB: Triángulos orientados hacia fuera",
            "Comprobado con el producto cruz y el centro de cada triángulo",
        )
        registrar_resultado(
            normales_coinciden,
            "GLB: Normales alineadas con los triángulos",
            "Las normales apuntan al mismo lado que las caras",
        )
    except Exception as err_normales:
        registrar_resultado(False, "GLB: Validación de normales e índices", f"Error: {err_normales}")


def main():
    """
    Punto de entrada principal para la verificación de artefactos en Prueba 001.
    """
    registrar_resultado(True, "INICIO", "Ejecutando verificador de exportación para BancaPET Prueba 001")

    raiz = obtener_raiz_proyecto()
    registrar_resultado(True, "CONFIGURACION", f"Directorio raíz detectado: {raiz}")

    ruta_fcstd = os.path.join(raiz, "cad", "cubo.FCStd")
    ruta_step = os.path.join(raiz, "cad", "cubo.step")
    ruta_glb = os.path.join(raiz, "modelos", "cubo.glb")
    ruta_glb_web = os.path.join(raiz, "web", "public", "models", "cubo.glb")

    # 1. Comprobación de existencia y contenido de archivos
    fcstd_existe = comprobar_existencia_y_tamano("cad/cubo.FCStd", ruta_fcstd)
    step_existe = comprobar_existencia_y_tamano("cad/cubo.step", ruta_step)
    glb_existe = comprobar_existencia_y_tamano("modelos/cubo.glb", ruta_glb)

    # 2. Validación de archivo FreeCAD (cad/cubo.FCStd)
    if fcstd_existe:
        validar_fcstd(ruta_fcstd)
    else:
        registrar_resultado(False, "FCStd: Inspección de geometría", "Omitida por ausencia o archivo vacío")

    # 3. Validación de archivo STEP (cad/cubo.step)
    if step_existe:
        validar_step(ruta_step)
    else:
        registrar_resultado(False, "STEP: Inspección en documento temporal", "Omitida por ausencia o archivo vacío")

    # 4. Validación de archivo GLB 2.0 (modelos/cubo.glb)
    if glb_existe:
        validar_glb(ruta_glb)
    else:
        registrar_resultado(False, "GLB: Inspección de contenedor y malla", "Omitida por ausencia o archivo vacío")

    # La copia servida por Vite debe corresponder al GLB maestro.
    try:
        with open(ruta_glb, "rb") as archivo_maestro:
            bytes_maestro = archivo_maestro.read()
        with open(ruta_glb_web, "rb") as archivo_web:
            bytes_web = archivo_web.read()
        registrar_resultado(
            bytes_maestro == bytes_web,
            "GLB: Copia web sincronizada",
            f"Maestro={len(bytes_maestro)} bytes, copia web={len(bytes_web)} bytes",
        )
    except Exception as err_copia:
        registrar_resultado(False, "GLB: Copia web sincronizada", f"No se pudieron comparar los archivos: {err_copia}")

    # 5. Evaluación final y reporte
    if LISTA_FALLAS:
        mensaje_resumen = (
            f"Validación finalizada con {len(LISTA_FALLAS)} comprobación(es) FALLIDA(S):\n"
            + "\n".join(f"  * {falla}" for falla in LISTA_FALLAS)
        )
        # Terminar con error no cero mediante excepción
        raise RuntimeError(mensaje_resumen)
    else:
        registrar_resultado(True, "RESUMEN FINAL", "Todas las comprobaciones PASARON exitosamente")


# Ejecución directa al invocar el macro
main()
